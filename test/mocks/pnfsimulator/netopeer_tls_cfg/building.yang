module building {
  yang-version 1.1;
  namespace "urn:building:test";

  prefix bld;

  organization "building";
  contact "my buildig address";
  description "yang model for building";
  revision "2018-02-13"{
    description "initial version";
  }

  container rooms{
    list room{
      key room-number;
      leaf room-number{
        type uint16;
      }
      leaf size {
        type uint32;
      }
    }

  }
}
